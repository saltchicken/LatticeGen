"""LatticeGen FreeCAD Macro Entry Point."""

import os
import sys

import FreeCAD as App
import FreeCADGui as Gui

# Dynamically add the macro directory to sys.path to enable package imports
macro_dir = os.path.dirname(os.path.abspath(__file__))
if macro_dir not in sys.path:
    sys.path.insert(0, macro_dir)

from latticegen.ui import PatternTaskPanel


def main():
    if Gui.Control.activeDialog():
        Gui.Control.closeDialog()

    selection = Gui.Selection.getSelectionEx()
    if not selection or not hasattr(selection[0].Object, "Shape"):
        App.Console.PrintError("Error: Select a valid solid object first.\n")
        return

    target_obj = selection[0].Object
    target_face = None

    if selection[0].HasSubObjects and "Face" in selection[0].SubElementNames[0]:
        target_face = target_obj.Shape.getElement(selection[0].SubElementNames[0])

    panel = PatternTaskPanel(target_obj, target_face)
    Gui.Control.showDialog(panel)


if __name__ == "__main__":
    main()
